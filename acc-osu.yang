module acc-osu {
    yang-version 1.1;
    namespace "urn:ccsa:yang:acc-osu";
    prefix acc-osu;
    import acc-yang-types {
         prefix acc-type; 
    }
    
    import acc-devm {
        prefix acc-devm;
    }
    
    import acc-connection {
        prefix acc-con;
    }

    import acc-otn {
        prefix acc-otn;
    }

    import acc-enum {
        prefix acc-enum;
    }

    import acc-protection-group {
        prefix acc-pg;
    }

    revision 2021-01-31 {
        description "for M-OTN 1.0";
    }

    
    identity OSU {
        base acc-type:layer-protocol-name;
    }
   
    typedef tcm-mode-type {
        type enumeration {
            enum operational{
                value 0;
                description "enable TCM";
            }
            enum monitor {
                value 1;
                description "monitor TCM";
            }
            enum transparent{
                value 2;
                description "disable TCM";
            }
        }
    }

    typedef fail-reason {
        type enumeration {
            enum service-fail{
                value 0;
                description "业务失败";
            }
            enum no-resource {
                value 1;
                description "资源不足";
            }
            enum timeout{
                value 2;
                description "定时器超时";
            }
        }
    }

    /*
   * groupings
   */
    

    augment "/acc-devm:ptps/acc-devm:ptp" {
        when "acc-devm:layer-protocol-name = 'acc-osu:OSU'";
        container osu-ptp-pac {
		leaf-list osu-signal-type {
			config false;
			min-elements 1;
			type acc-enum:signal-type;
		}
		leaf-list adaptation-type {
			config false;
			type acc-enum:adaptation-type;
		}
        }
    }

    augment "/acc-devm:ftps/acc-devm:ftp" {
        when "acc-devm:layer-protocol-name = 'acc-osu:OSU'";
        container osu-ftp-pac {
            leaf available-tpn-number {
                    mandatory true;
                    type uint64;
		    description "可用TPN 0~1000";
		}
		leaf total-band-width {
			mandatory true;
			type uint64;
			description "所支持的OSU基准带宽单元(10.4Mbps)数量，与对应ODU类型相关";
		}
		leaf available-band-width {
			mandatory true;
			type uint64;
			description "当前可用OSU基准带宽单元(10.4Mbps)数量";
		}
        }
    }

    augment "/acc-devm:ctps/acc-devm:ctp" {
        when "acc-devm:layer-protocol-name = 'acc-osu:OSU'";
        container osu-ctp-pac {
            leaf osu-signal-type {
                type acc-enum:signal-type;
                description "";
            }
            leaf adaptation-type {
                type acc-enum:adaptation-type;
                description "";
            }
		leaf tpn {
			mandatory true;
			type uint64;
			description "TPN的编号0～1000";
		}
		leaf bandwidth {
			config false;
			type uint64;
			description "CTP占用的OSU基准单元的数量";
		}
		leaf pm-trail-trace-actual-tx {
			type string;
		}
		leaf pm-trail-trace-actual-rx {
			type string;
		}
		leaf pm-trail-trace-expected-tx {
			type string;
		}
		leaf tcm1-mode {
			type tcm-mode-type;
		}
		leaf tcm2-mode {
			type tcm-mode-type;
		}
        }
    }

    rpc osu-two-way-dm {
        input {
            leaf ctp-name {
	    	mandatory true;
                type string;
            }
            leaf dm-type {
	    	mandatory true;
                type string;
                description "PM or TCM1";
            }
        }
        output {
            leaf osu-delay {
	    	mandatory true;
                type uint64;
            }
        }
    }



    rpc create-eo-osu-connection{
        input {
        uses acc-con:create-connection;
            
            leaf uni-protection-type {
                type acc-pg:protection-type;
                description "default lag";
            }
            leaf nni-protection-type {
                type acc-pg:protection-type;
            }
            container eth-uni {
                leaf uni-ptp-name {
                    mandatory true;
                    type string;
                }
                leaf second-uni-ptp-name {
                    type string;
                    description "可选，LAG保护（非负载均衡，单端保护）";
                }
                container client-vlan-spec {
                  when "../../service-type = 'EVPL'";
                    uses acc-con:vlan-spec;
                    description "只适用于EVPL，指定C-VLAN，用于客户Vlan与运营商Vlan的匹配，无需携带accessAction。不携带该参数时表示端口匹配";
                }
                container uni-vlan-spec {
                  when "../../service-type = 'EVPL'";
                    uses acc-con:vlan-spec;
                    description "只适用于EVPL，用于在客户VLAN交换的情况下，指定C-VLAN, 默认CTAG";
                }
            }

            container primary-nni {
                uses acc-otn:nni;
		leaf tpn {
            		type uint64;
            		description "value Range: 1~1000";
        	}
                description "primary nni,必选";
            }
            container secondary-nni {
                uses acc-otn:nni;
		leaf tpn {
            		type uint64;
            		description "value Range: 1~1000";
        	}
                description "业务带保护模式，可选";
            }
              
        }
        output {
            container connection {
                uses acc-con:connection;
            }
            container create-component {
                leaf-list ftp-name {
                    type string {
                        length "1..64";
                    }
                }
                leaf-list ctp-name {
                    type string {
                        length "1..64";
                    }
                }
            }
	    container ports-with-role {
	    leaf eth-ptp-ctp {
			    type string;
                mandatory true;
				description "客户侧 PTP的CTP";
			}
			leaf eth-ftp-ctp {
			    type string;
                mandatory true;
				description "ETH FTP的clientCtp";
			}
			leaf eth-ftp {
			    type string;
                mandatory true;
				description "ETH FTP";
			}
		    leaf eth-ftp-osu-ctp {
			    type string;
                mandatory true;
				description "ETH FTP绑定的serverCtp";
			}
		    leaf osu-ftp {
			type string;
			mandatory true;
			description "OSU FTP(主)";
		    }
			leaf osu-ftp-ctp {
			    type string;
		mandatory true;
				description "OSU FTP(主)的clientCtp";
			}
		    leaf osu-ftp-p {
			type string;
			description "OSU FTP(备)(only SNCP）";
		    }
		    leaf osu-ftp-ctp-p {
			    type string;
				description "OSU FTP(备)的clientCtp（only SNCP）";
			}
	    	leaf ul-odu-ctp {
		   	 type string;
		 	mandatory true;
			description "上联 ODU CTP(主)";
		}
		leaf ul-odu-ctp-p {
		    type string;
			description "上联 ODU CTP(备)(SNCP or ODU)";
		}
	    }
        }
    }

    rpc create-osu-connection {
        input {
            uses acc-con:create-connection;
            leaf uni-protection-type {
                type acc-pg:protection-type;
                description "for UNI-NNI 若有保护则: msp";
            }
            leaf nni-protection-type {
                type acc-pg:protection-type;
                description "若有保护则: osu-sncp-i";
            }
            leaf nni2-protection-type {
                type acc-pg:protection-type;
                description "for NNI-NNI 若有保护则: osu-sncp-i";
            }
            container uni {
                leaf uni-ptp-name {
                    type string;
                }
                leaf second-uni-ptp-name {
                    type string;
                }
        		leaf client-signal-type {
        			type acc-enum:signal-type;
        		}
                description "for UNI-NNI";
            }

            container primary-nni {
                uses acc-otn:nni;
		leaf tpn {
            		type uint64;
            		description "value Range: 1~1000";
        	}
                description "primary nni,必选";
            }
            container secondary-nni {
                uses acc-otn:nni;
		leaf tpn {
            		type uint64;
            		description "value Range: 1~1000";
        	}
                description "带保护模式，可选";
            }
            container primary-nni2 {
                uses acc-otn:nni;
		leaf tpn {
            		type uint64;
            		description "value Range: 1~1000";
        	}
                description "NNI-NNI不带保护，可选";
            }
            container secondary-nni2 {
                uses acc-otn:nni;
		leaf tpn {
            		type uint64;
            		description "value Range: 1~1000";
        	}
                description "NNI-NNI带保护，可选";
            }
        }
        output {
            container connection {
                uses acc-con:connection;
            }
            container create-component {
                leaf-list ftp-name {
                    type string {
                        length "1..64";
                    }
                }
                leaf-list ctp-name {
                    type string {
                        length "1..64";
                    }
                }                
            }
	    container ports-with-role {
	    	leaf osu-ptp-ctp {
                        type string;
                        description "客户侧 PTP的子CTP(only UNI-NNI)";
                    }
                    leaf ul-osu-ftp {
                        mandatory true;
                        type string;
                        description "OSU FTP(主)";
                    }
                    leaf ul-osu-ftp-ctp {
                        mandatory true;
                        type string;
                        description "OSU FTP(主)的子CTP";
                    }
                    
                    leaf ul-osu-ftp-p {
                        type string;
                        description "OSU FTP(备)(only SNCP)";
                    }
                    leaf ul-osu-ftp-ctp-p {
                        type string;
                        description "OSU FTP(备)的子CTP (only SNCP)";
                    }
                    leaf dl-odu-ctp {
                        type string;
                        description "下联ODU CTP(主)(only NNI-NNI)";
                    }
                    leaf dl-odu-ctp-p {
                        type string;
                        description "下联ODU CTP(备)(only NNI-NNI）";
                    }
                    leaf dl-osu-ftp {
                        type string;
                        description "下联OSU FTP(主)";
                    }
                    leaf dl-osu-ftp-ctp {
                        type string;
                        description "下联OSU FTP(主)的子CTP";
                    }
                    leaf dl-osu-ftp-p {
                        type string;
                        description "下联OSU FTP(备)（only NNI-NNI SNCP）";
                    }
                    leaf dl-osu-ftp-ctp-p {
                        type string;
                        description "下联OSU FTP(备)的子CTP(only NNI-NNI SNCP）";
                    }
                    
                    leaf ul-odu-ctp {
                        mandatory true;
                        type string;
                        description "上联ODU CTP(主)";
                    }
                    leaf ul-odu-ctp-p {
                        type string;
                        description "上联ODU CTP(备)(有保护时必须报）";
                    }
	    }
        }
    }
	
	
    rpc modify-osu-connection-capacity {
        input {
            leaf ctp-name {
	    	mandatory true;
                type string;
            }
            uses acc-con:capacity;
            leaf timer {
	    	mandatory true;
                type uint64;
                description "default 60   range:1~1023";
            }
            leaf action {
	    	mandatory true;
                type acc-otn:modify-action;
            }
        }
    }

    notification osu-adjustment-notification {
        leaf osu-adjust-serial-no {
            mandatory true;
            type uint64;
            
        }
        leaf ctp-name {
            mandatory true;
            type string {
                length "1..64";
            }
        }
        leaf modify-result {
            mandatory true;
            type string;
            description "success , failure";
        }
        leaf fail-reason {
            type fail-reason;
            description "if only failure";
        }
        container requested-capacity {
            uses acc-con:capacity;
        }
    }
}
