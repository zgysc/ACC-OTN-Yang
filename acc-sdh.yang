module acc-sdh {
    yang-version 1.1;
    namespace "urn:ccsa:yang:acc-sdh";
    prefix acc-sdh;

    import acc-devm { 
        prefix acc-devm; 
    }
    import acc-connection {
        prefix acc-con;
    }
    import acc-otn {
        prefix acc-otn;
    }
    import acc-yang-types {
        prefix acc-type;
    }

    import acc-enum {
        prefix acc-enum;
    }

    import acc-protection-group {
        prefix acc-pg;
    }

    revision 2021-01-31 {
        description "for M-OTN 1.0";
    }

    identity SDH {
        base acc-type:layer-protocol-name;
    }
    

    grouping vcg-pac {
        leaf vc-type {
            mandatory true;
            type acc-enum:sdh-switch-type;
        }
        leaf lcas {
            type boolean;
            default false;
        }
        leaf hold-off {
            type uint32;
            default 0;
            description "unit: ms";
        }
        leaf wtr {
            type uint32;
            default 300;
            description "unit: s";
        }
        leaf tsd {
            type boolean;
            default false;
        }
        leaf tx-number {
            type uint64;
            default 0;
            config false;
            description "The actual number of members sent by the LCAS group.";
        }
        leaf rx-number {
            type uint64;
            default 0;
            config false;
            description "The actual number of members received by the LCAS group.";
        }
        leaf so-handshake-state {
            type boolean;
            default false;
            config false;
            description "The handshake state of the source end.";
        }
    }

    grouping sdh-ftp {
        leaf sdh-type {
            mandatory true;
            type acc-enum:signal-type;
        }
        leaf vc-type {
            mandatory true;
            type acc-enum:sdh-switch-type;
        }
        leaf mapping-path {
            mandatory true;
            type string {
                length "1..64";
            }
        }

    }

    /*augment "/acc-devm:eqs/acc-devm:eq" {
        container eq-sdh-pac {
            leaf-list supported-sdh-signal-types {
                type acc-enum:signal-type;
                config false;
            }
            leaf-list switch-capability {
                type acc-enum:sdh-switch-type;
                config false;
            }
        }
    }*/
    augment "/acc-devm:ptps/acc-devm:ptp" {
        container sdh-mapping-pac {
            leaf-list supported-sdh-signal-types {
                type acc-enum:signal-type;
            }
            leaf-list switch-capability {
                type acc-enum:sdh-switch-type;
            }
        }
    }
    
    augment "/acc-devm:ptps/acc-devm:ptp" {
        when "acc-devm:layer-protocol-name = 'acc-sdh:SDH'";
        container sdh-ptp-pac {
            leaf current-sdh-signal-type {
                mandatory true;
                type acc-enum:signal-type;
            }
            leaf-list supported-sdh-signal-types {
                type acc-enum:signal-type;
                config false;
            }
            leaf-list switch-capability {
                min-elements 1;
                type acc-enum:sdh-switch-type;
                config false;
            }
            leaf j0-actual-tx {
                type string {
                    length "1..64";
                }
            }
            leaf j0-expected-rx {
                type string {
                    length "1..64";
                }
            }
            leaf j0-actual-rx {
                type string {
                    length "1..64";
                }
                config false;
            }
        }

        
    }

    augment "/acc-devm:ftps/acc-devm:ftp" {
        when "acc-devm:layer-protocol-name = 'acc-sdh:SDH'";
        container sdh-ftp-pac {
            leaf sdh-signal-type {
                mandatory true;
                type acc-enum:signal-type;
            }
            leaf-list switch-capability {
                min-elements 1;
                type acc-enum:sdh-switch-type;
                config false;
            }
            leaf service-mapping-mode {
                type acc-enum:adaptation-type;
            }
            leaf j0-actual-tx {
                type string {
                    length "1..64";
                }
            }
            leaf j0-expected-rx {
                type string {
                    length "1..64";
                }
            }
            leaf j0-actual-rx {
                type string {
                    length "1..64";
                }
                config false;
            }
        }
    }

    augment "/acc-devm:ctps/acc-devm:ctp" {
        when "acc-devm:layer-protocol-name = 'acc-sdh:SDH'";
        container vc-ctp-pac {
            leaf vc-type {
                mandatory true;
                type acc-enum:sdh-switch-type;
            }
            leaf mapping-path {
                mandatory true;
                type string {
                    length "1..64";
                }
            }
            leaf j1-actual-tx {
                type string {
                    length "1..64";
                }
            }
            leaf j1-expected-rx {
                type string {
                    length "1..64";
                }
            }
            leaf j1-actual-rx {
                type string {
                    length "1..64";
                }
                config false;
            }
        }
    }

    /*
    * operations
    */

    rpc create-sdh-connection {
        input {
            uses acc-con:create-connection;
            leaf service-mapping-mode {
                type acc-enum:adaptation-type;
            }
            leaf uni-protection-type {
                type acc-pg:protection-type;
                description "default msp-1-plus-1";
            }
            leaf nni-protection-type {
                type acc-pg:protection-type;
            }
            leaf nni2-protection-type {
                type acc-pg:protection-type;
            }
            container sdh-uni {
                leaf uni-ptp-name {
                    type string {
                        length "1..64";
                    }
                }
                leaf vc-type {
                    type acc-enum:sdh-switch-type;
                }
                leaf mapping-path {
                    type string {
                        length "1..64";
                    }
                }
                description "only for UNI-NNI ";
            }
            container second-sdh-uni {
                leaf uni-ptp-name {
                    type string {
                        length "1..64";
                    }
                }
                leaf vc-type {
                    type acc-enum:sdh-switch-type;
                }
                leaf mapping-path {
                    type string {
                        length "1..64";
                    }
                }
                description "only for UNI-NNI ";
            }
            
            container primary-nni {
                uses acc-otn:nni;
                container sdh-ftp {
                    uses sdh-ftp;
                }
                description "primary nni, mandatory true";
            }
            container secondary-nni {
                uses acc-otn:nni;
                container sdh-ftp {
                    uses sdh-ftp;
                }
                description "only for service with protection. Optional";
            }
            container primary-nni2 {
                uses acc-otn:nni;
                container sdh-ftp {
                    uses sdh-ftp;
                }
                description "only NNI2NNI mode, optional!";
            }
            container secondary-nni2 {
                uses acc-otn:nni;
                container sdh-ftp {
                    uses sdh-ftp;
                }
                description "only NNI2NNI mode and with protection. optional";
            }
        }
        output {
            container connection {
                uses acc-con:connection;
            }
            container create-component {
                leaf-list ftp-name {
                    min-elements 1;
                    type string {
                        length "1..64";
                    }
                }
                leaf-list ctp-name {
                    min-elements 1;
                    type string {
                        length "1..64";
                    }
                }                
            }
            container ports-with-role{
                leaf sdh-ptp-ctp {
                type string;
                description "客户侧 PTP 的子 CTP(for UNI-NNI)";
              }

              leaf ul-sdh-ftp {
                mandatory true;
                type string;
                description "SDH FTP(主)";
              }

              leaf ul-sdh-ftp-ctp {
                mandatory true;
                type string;
                description "SDH FTP(主)的SDH CTP";
              }

              leaf ul-sdh-ftp-p {
                type string;
                description "SDH FTP(备) 有保护才上报";
              }

              leaf ul-sdh-ftp-ctp-p {
                type string;
                description "SDH FTP(备)的SDH CTP(有保护才上报)";
              }

              leaf dl-sdh-ftp {
                type string;
                description "下联 SDH FTP(主) (for NNI-NNI)";
              }

              leaf dl-sdh-ftp-ctp {
                type string;
                description "下联 SDH FTP(主)的SDH CTP (for NNI-NNI)";
              }

              leaf dl-sdh-ftp-p {
                type string;
                description "下联 SDH FTP(备)(for NNI-NNI有保护才上报)";
              }

              leaf dl-sdh-ftp-ctp-p {
                type string;
                description "下联 SDH FTP(备)的SDH CTP(for NNI-NNI有保护才上报)";
              }

              leaf ul-odu-ctp {
                mandatory true;
                type string;
                description "上联 ODU CTP(主)";
              }
              leaf ul-odu-ctp-p {
                type string;
                description "上联 ODU CTP(备)（有保护则上报）";
              }
              leaf dl-odu-ctp {
                type string;
                description "下联 ODU CTP(主)（only NNI-NNI）";
              }
              leaf dl-odu-ctp-p {
                type string;
                description "下联 ODU CTP(备)（only NNI-NNI有保护才上报）";
              }
            }
        }
    }
    
    
}
